# TMR_Single_Motor_Requirements

## #1: AMK Derating Factor (Functional)
The motor derating factor is calculated by the motor controller.
The motor derating factor is not available to the VCU, so the factor must be calculated by the VCU, based on the algorithm described in 8.2.8 Torque limitation in the AMK Inverters documentation.
There are many factors which determine the motor derating factor, and the most limiting factor is used to determine the motor derating factor. So, the factors have indepedent effects on the motor derating factor.
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
### #2: Motor temperature (Functional)
The motor derating factor is 1 until a temperature of 125 °C (motor parameter ID32798 - 11).
The motor derating factor is linearly decreased until a temperature of 140 °C, where the derating factor is 0 (motor parameter ID32798 - 12).

### #3: Inverter power supply (IGBT) temperature (Functional)
The motor derating factor is 1 until a temperature of 115 °C (motor parameter ID32798 - 8).
The motor derating factor is linearly decreased until a temperature of 125 °C, where the derating factor is 0 (motor parameter ID32798 - 9).

### #4: Inverter cold plate temperature (Functional)
The motor derating factor is 1 until a temperature of 50 °C (motor parameter ID32798 - 5).
The motor derating factor is linearly decreased until a temperature of 60 °C, where the derating factor is 0 (motor parameter ID32798 - 6).

### #8: Overvoltage (Functional)
The motor derating factor is 1 until a battery voltage of 5% less than 580 VDC (motor parameter ID32798 - 7).
The motor derating factor is linearly decreased until a battery voltage of 580 VDC, where the derating factor is 0 (motor parameter ID32798 - 3).

### #9: Undervoltage (Functional)
The motor derating factor is 1 until a battery voltage of 250 VDC (motor parameter ID32798 - 10).
The motor derating factor is linearly decreased until a battery voltage of 120 VDC, where the derating factor is 0 (motor parameter ID32798 - 4).

### #14: AMK Current overload protection (Functional)
The AMK Inverters provide I2t protection for the motors and the inverters.
The I2t protection for the inverters cannot be disabled.
The I2t protection for the motors are activated by setting ID32773 'Service bits', bit 14 to be equal to 1.
Refer to the following link to learn how I2t protection works.
http://www.technosoft.ro/KB/index.php?/article/AA-00216/20/Drive-Commissioning/Protections/I2t-Protection-Drive-Setup-GB-CM.html

#### #5: Overload as per inverter current integral (Functional)
I2t protection is used to protect the inverters.
The derating factor is equal to 1 when the overload threshold value is equal to 0.
The derating factor is equal is linearly decreased to 0 until a overload threshold value of 1.

##### #10: Inverter current overload derating factor (Functional)
The derating factor is equal to 1 when the overload threshold value is equal to 0.
The derating factor is equal is linearly decreased to 0 until a overload threshold value of 1.

##### #12: Inverter i2t Calculation (Functional)

#### #6: Overload as per motor current integral (Functional)
I2t protection is used to protect the motors.
The derating factor is equal to 1 when the overload threshold value is equal to 0.
The derating factor is equal is linearly decreased to 0 until a overload threshold value of 1.

##### #11: Motor current overload derating factor (Functional)
The derating factor is equal to 1 when the overload threshold value is equal to 0.
The derating factor is equal is linearly decreased to 0 until a overload threshold value of 1.

##### #13: Motor i2t Calculation (Functional)
