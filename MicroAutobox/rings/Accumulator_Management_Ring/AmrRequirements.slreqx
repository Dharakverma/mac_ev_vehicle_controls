# AmrRequirements

## #9: Accumulator Fault Handling

### #8: Voltage Violation Check
If the average voltage of the accumulator for the previous 500 ms is greater than 600V, a fault should be triggered.
If a fault has occured, the output should be forever latched to TRUE.

#### #14: Average Voltage Violation Check
If the average voltage of the accumulator for the previous 500 ms is greater than 600V, a fault should be triggered.
Also, if a fault has occured, the output should be forever latched.

#### #18: Continuous Voltage Violation Check
If the continuous voltage of the accumulator for the previous 100 ms is greater than 600V, a fault should be triggered.
Also, if a fault has occured, the output should be forever latched.

### #22: Power Violation Check
If the average power drawn of the accumulator for the previous 500 ms is greater than 80kW, a fault should be triggered.
Also, if a fault has occured, the output should be forever latched.

#### #23: Average Voltage Violation Check
If the average power drawn from the accumulator for the previous 500 ms is greater than 80kW, a fault should be triggered.
Also, if a fault has occured, the output should be forever latched.

#### #24: Continuous Voltage Violation Check
If the continuous power drawn from the accumulator for the previous 100 ms is greater than 80kW, a fault should be triggered.
Also, if a fault has occured, the output should be forever latched.

### #25: Over Voltage

### #27: Under Voltage

### #28: Bank/Cell Communication Fault

### #29: Over Temperature

### #30: Excessive Precharge Time

### #31: EEPROM Stack Overflow

### #32: Relay Fault

### #33: No Battery Voltage

### #34: Contactors

#### #35: Shorted Contactors

#### #36: Open Contactors

## #10: Current Limits
The discharge and charge current limits must be equal to the limits reported by the AMS.
The charge current limit is determined by the CCL and HLIM.
The discharge current limit is determined by the DCL and LLIM.

### #3: Discharge Current Limit (DCL)
The discharge current must be equal to the DCL reported by the AMS.

### #7: Charge Current Limit (CCL)
The charging current must be equal to the CCL reported by the AMS.

### #12: High Limit (HLIM)
The charge current limit shoud be equal to zero if HLIM is active.

### #13: Low Limit (LLIM)
The discharge current limit shoud be equal to zero if LLIM is active.

## #37: AMR State Machine
The AMR must have the following modes:
- OFF
- STARTUP
- RUNNING
- SHUTDOWN

### #38: OFF Mode
In this mode, the ring status must be OFF.

### #39: STARTUP Mode
The mode must only be entered if:
- the MSR makes a high voltage startup request
- AMR is in the OFF mode

#### #42: Close Contactor Request
The ring status must be startup HV in progress before the close contactor request is made.
This mode must make a close contactor request and check that the precharge circuit is enabled and then check that positive and negative contactors are closed. If so, the ring status must be startup HV completed.

### #43: RUNNING Mode
The mode must only be entered if:
- the MSR makes a running mode request
- AMR has completed its HV startup
- AMR is in the startup mode
The AMR should standby in this mode.

### #45: SHUTDOWN Mode
The mode must only be entered if:
- the MSR makes a high voltage startup request
- AMR is in the OFF mode

#### #46: Open Contactor Request
The ring status must be shutdown HV in progress before the open contactor request is made.
This mode must make a contactor request and check that the all contactors are open. If so, the ring status must be shutdown HV completed.
